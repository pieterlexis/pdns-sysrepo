/*
 * Copyright 2019-2020 Pieter Lexis <pieter.lexis@powerdns.com>
 *
 * Licensed under the Apache License, Version 2.0 (the "License");
 * you may not use this file except in compliance with the License.
 * You may obtain a copy of the License at
 *
 * http://www.apache.org/licenses/LICENSE-2.0
 *
 * Unless required by applicable law or agreed to in writing, software
 * distributed under the License is distributed on an "AS IS" BASIS,
 * WITHOUT WARRANTIES OR CONDITIONS OF ANY KIND, either express or implied.
 * See the License for the specific language governing permissions and
 * limitations under the License.";
 */
module dns-common {
    yang-version "1.1";
    namespace "http://powerdns.com/yang/dns-common";
    prefix dnsc;

    import ietf-inet-types {
      prefix inet;
    }

    organization
      "PowerDNS.COM BV";
    contact
      "Pieter Lexis <mailto:pieter.lexis@powerdns.com>";

    typedef owner-name {
        // TODO support IDN (xn--XX-XXXX)
        // TODO support symbols other than - and _
        description
          "The owner name must be a valid dns name for the owner of a resource record.
           It can start with a '*' to denote a wildcard and must end with a '.'";

        type string {
            length "1..255";
            pattern
              '(\*\.)?([a-z0-9_][-a-z0-9_]{0,61}[a-z0-9]\.)+|\.';
            pattern
              ".*--.*" {
                modifier invert-match;
            }
        }
    }

    typedef zone-name {
        type owner-name {
            pattern
              '([a-z0-9_][-a-z0-9_]{0,63}\.)+|\.';
        }
    }

    typedef host-name {
        type zone-name {
            pattern
              '([a-z0-9]([-a-z0-9_]{0,61}[a-z0-9])\.){2,}';
        }
    }

    grouping dns-endpoint {
        leaf address {
            type inet:ip-address-no-zone;
            mandatory true;
        }
        leaf port {
            type inet:port-number;
            default 53;
        }
    }

}
