/*
 * Copyright 2019-2020 Pieter Lexis <pieter.lexis@powerdns.com>
 *
 * Licensed under the Apache License, Version 2.0 (the "License");
 * you may not use this file except in compliance with the License.
 * You may obtain a copy of the License at
 *
 * http://www.apache.org/licenses/LICENSE-2.0
 *
 * Unless required by applicable law or agreed to in writing, software
 * distributed under the License is distributed on an "AS IS" BASIS,
 * WITHOUT WARRANTIES OR CONDITIONS OF ANY KIND, either express or implied.
 * See the License for the specific language governing permissions and
 * limitations under the License.";
 */

module dns-common-typedef-test {
    yang-version 1.1;
    namespace "http://powerdns.com/yang/dns-common-typedef-test";
    prefix dns-common-typedef-test;

    import dns-common {
        prefix dnsc;
    }


    organization
      "PowerDNS.COM BV";
    contact
      "Pieter Lexis <mailto:pieter.lexis@powerdns.com>";

    description
      "This module is only used for testing the typedefs in dns-common";

    revision 2020-01-23 {
      description "initial";
    }

    container hostnames {
        leaf-list hostname {
            type dnsc:host-name;
        }
    }

    container zonenames {
        leaf-list zonename {
            type dnsc:zone-name;
        }
    }

    container ownernames {
        leaf-list owner-name {
            type dnsc:owner-name;
        }
    }
}
